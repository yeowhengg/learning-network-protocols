module "openconfig-hercules-interfaces" {
	yang-version "1";
	namespace "http://openconfig.net/yang/hercules/interfaces";
	prefix "herc-if";
	import "openconfig-interfaces" {
		prefix "oc-if";
	}
	import "openconfig-if-ethernet" {
		prefix "oc-eth";
	}
	import "openconfig-extensions" {
		prefix "oc-ext";
	}
	organization "OpenConfig Hercules Working Group";
	contact "openconfig-hercules@googlegroups.com";
	description "Hercules extensions to OpenConfig interface model.";
	oc-ext:openconfig-version "0.2.0";
	revision "2018-06-01" {
		description "Initial version.";
		reference "0.2.0";
	}
	grouping "hercules-interface-eth-config" {
		description "Configuration data for Hercules Ethernet interfaces.";
		leaf "forwarding-viable" {
			type "boolean";
			default "true";
			description "This value indicates whether the interface may be used
			             to route traffic or not.  If set to false, the
			             interface is not used for forwarding traffic, but as long as
			             it is up, the interface still maintains its layer-2
			             adjacencies and runs its configured layer-2 functions
			             (e.g., LLDP, etc.).
			             
			             This is used by the controller to disable an interface
			             (usually part of an aggregate) for the purposes of forwarding
			             traffic. This allows a logical aggregate to continue to be
			             used with partial capacity, for example.  Note that setting
			             `forwarding-viable = false` is not equivalent to
			             administratively disabling the interface -- in particular, the
			             interface is expected to participate in L2 protocols such as
			             LLDP or LACP even if it blocked from forwarding traffic.";
		}
	}
	grouping "hercules-interface-config" {
		description "Configuration data for Hercules interfaces";
		leaf "id" {
			type "uint32";
			description "The numeric identifier used by the controller to address the
			             interface.  This id is assigned by the SDN management system
			             to establish an externally deterministic numeric reference
			             (SDN port number) for the interface.  The management system
			             must ensure that the id is unique within the required
			             context (e.g., with respect to the node on which the
			             interface resides).
			             
			             Note that this identifier is used when a numeric reference
			             to the interface is required.  It does not replace the
			             unique name assigned to the interface.";
		}
		leaf "health-indicator" {
			type "enumeration" {
				enum "GOOD" {
					description "Sets the indicator to show the interface health, for
					             the purposes of protocol operations, is good / normal.";
				}
				enum "BAD" {
					description "Sets the indicator to show that the interface health,
					             for the purposes of protocol operations, is
					             bad / failed.";
				}
			}
			description "This allows a management or control system to set the health
			             state of an interface for the purposes of protocol
			             operations.  The state can be used to set indicators, such
			             as as a port LED, to visually indicate its health.  If the
			             interface is part of a channelized physical port, the device
			             should consider the health across all associated
			             interfaces, and set the port LED accordingly.  The health
			             indicator applies to physical interfaces such as Ethernet
			             interfaces, not logical interfaces such as routed VLANs or
			             loopbacks.
			             
			             A switch implementation may map `GOOD` and `BAD`
			             values to appropriate LED colors, for example red and green,
			             respectively, on the physical port corresponding to the
			             interface.";
		}
	}
	grouping "hercules-interface-state" {
		description "Hercules-specific operational state data";
	}
	augment "/oc-if:interfaces/oc-if:interface/oc-if:config" {
		description "Adds Hercules-specific configuration to the interface module";
		uses "hercules-interface-config";
	}
	augment "/oc-if:interfaces/oc-if:interface/oc-if:state" {
		description "Adds Hercules-specific status information to the interface module";
		uses "hercules-interface-config";
		uses "hercules-interface-state";
	}
	augment "/oc-if:interfaces/oc-if:interface/oc-eth:ethernet/oc-eth:config" {
		description "Augments Hercules-specific configuration data for Ethernet
		             interfaces.";
		uses "hercules-interface-eth-config";
	}
	augment "/oc-if:interfaces/oc-if:interface/oc-eth:ethernet/oc-eth:state" {
		description "Augments Hercules-specific operational state data for Ethernet
		             interfaces.";
		uses "hercules-interface-eth-config";
	}
}
